-- ASN1START
-- **************************************************************
--
-- Elementary Procedure definitions
-- Derived from 3GPP 38.413 v15.4.0 NGAP
-- **************************************************************
E2AP-PDU-Descriptions {
iso(1) identified-organization(3) dod(6) internet(1) private(4) enterprise(1) 53148 e2(1) version2 (2)e2ap(1) e2ap-PDU-Descriptions (0) }
DEFINITIONS AUTOMATIC TAGS ::=
BEGIN
-- **************************************************************
--
-- IE parameter types from other modules.
--
-- **************************************************************
IMPORTS
Criticality,
ProcedureCode
FROM E2AP-CommonDataTypes
E2connectionUpdate,
E2connectionUpdateAcknowledge,
E2connectionUpdateFailure,
E2nodeConfigurationUpdate,
E2nodeConfigurationUpdateAcknowledge,
E2nodeConfigurationUpdateFailure, E2setupFailure,
E2setupRequest,
E2setupResponse,
ErrorIndication,
ResetRequest, ResetResponse,
RICcontrolAcknowledge,
RICcontrolFailure,
RICcontrolRequest,
RICindication,
RICserviceQuery,
RICserviceUpdate,
RICserviceUpdateAcknowledge,
RICserviceUpdateFailure,
RICsubscriptionFailure,
RICsubscriptionRequest,
RICsubscriptionResponse,
RICsubscriptionDeleteFailure,
RICsubscriptionDeleteRequest,
RICsubscriptionDeleteResponse,
RICsubscriptionDeleteRequired
FROM E2AP-PDU-Contents
id-E2connectionUpdate,
id-E2nodeConfigurationUpdate,
id-E2setup,
id-ErrorIndication,
id-Reset,
id-RICcontrol,
id-RICindication,
id-RICserviceQuery,
id-RICserviceUpdate,
id-RICsubscription,
id-RICsubscriptionDelete,
id-RICsubscriptionDeleteRequired
FROM E2AP-Constants;
-- **************************************************************
--
-- Interface Elementary Procedure Class
--
-- **************************************************************
E2AP-ELEMENTARY-PROCEDURE ::= CLASS {
&InitiatingMessage ,
&SuccessfulOutcome OPTIONAL ,
&UnsuccessfulOutcome OPTIONAL ,
&procedureCode ProcedureCode UNIQUE ,
&criticality Criticality DEFAULT ignore
}
WITH SYNTAX {
INITIATING MESSAGE &InitiatingMessage
[SUCCESSFUL OUTCOME &SuccessfulOutcome]
[UNSUCCESSFUL OUTCOME &UnsuccessfulOutcome]
PROCEDURE CODE &procedureCode
[CRITICALITY &criticality]
}
-- **************************************************************
--
-- Interface PDU Definition
--
-- **************************************************************
E2AP-PDU ::= CHOICE {
initiatingMessage InitiatingMessage,
successfulOutcome SuccessfulOutcome,
unsuccessfulOutcome UnsuccessfulOutcome,
...
}
InitiatingMessage ::= SEQUENCE {
procedureCode E2AP-ELEMENTARY-PROCEDURE.&procedureCode ({E2AP-ELEMENTARY-PROCEDURES}),
criticality E2AP-ELEMENTARY-PROCEDURE.&criticality ({E2AP-ELEMENTARY-PROCEDURES}{@procedureCode}),
value E2AP-ELEMENTARY-PROCEDURE.&InitiatingMessage ({E2AP-ELEMENTARY-PROCEDURES}{@procedureCode})
}
SuccessfulOutcome ::= SEQUENCE {
procedureCode E2AP-ELEMENTARY-PROCEDURE.&procedureCode ({E2AP-ELEMENTARY-PROCEDURES}),
criticality E2AP-ELEMENTARY-PROCEDURE.&criticality ({E2AP-ELEMENTARY-PROCEDURES}{@procedureCode}),
value E2AP-ELEMENTARY-PROCEDURE.&SuccessfulOutcome ({E2AP-ELEMENTARY-PROCEDURES}{@procedureCode})
}
UnsuccessfulOutcome ::= SEQUENCE {
procedureCode E2AP-ELEMENTARY-PROCEDURE.&procedureCode ({E2AP-ELEMENTARY-PROCEDURES}),
criticality E2AP-ELEMENTARY-PROCEDURE.&criticality ({E2AP-ELEMENTARY-PROCEDURES}{@procedureCode}),
value E2AP-ELEMENTARY-PROCEDURE.&UnsuccessfulOutcome ({E2AP-ELEMENTARY-PROCEDURES}{@procedureCode})
}
-- **************************************************************
--
-- Interface Elementary Procedure List
--
-- **************************************************************
E2AP-ELEMENTARY-PROCEDURES E2AP-ELEMENTARY-PROCEDURE ::= {
E2AP-ELEMENTARY-PROCEDURES-CLASS-1 |
E2AP-ELEMENTARY-PROCEDURES-CLASS-2,
...
}
E2AP-ELEMENTARY-PROCEDURES-CLASS-1 E2AP-ELEMENTARY-PROCEDURE ::= {
ricSubscription |
ricSubscriptionDelete |
ricServiceUpdate |
ricControl |
e2setup |
e2nodeConfigurationUpdate |
e2connectionUpdate |
reset,
...
}
E2AP-ELEMENTARY-PROCEDURES-CLASS-2 E2AP-ELEMENTARY-PROCEDURE ::= {
ricIndication |
ricServiceQuery |
errorIndication |
ricSubscriptionDeleteRequired,
...
}
-- **************************************************************
--
-- Interface Elementary Procedures
--
-- **************************************************************
-- New for v01.01
e2connectionUpdate E2AP-ELEMENTARY-PROCEDURE ::= {
INITIATING MESSAGE E2connectionUpdate
SUCCESSFUL OUTCOME E2connectionUpdateAcknowledge
UNSUCCESSFUL OUTCOME E2connectionUpdateFailure
PROCEDURE CODE id-E2connectionUpdate
CRITICALITY reject
}
e2nodeConfigurationUpdate E2AP-ELEMENTARY-PROCEDURE ::= {
INITIATING MESSAGE E2nodeConfigurationUpdate
SUCCESSFUL OUTCOME E2nodeConfigurationUpdateAcknowledge
UNSUCCESSFUL OUTCOME E2nodeConfigurationUpdateFailure
PROCEDURE CODE id-E2nodeConfigurationUpdate
CRITICALITY reject
}
e2setup E2AP-ELEMENTARY-PROCEDURE ::= {
INITIATING MESSAGE E2setupRequest
SUCCESSFUL OUTCOME E2setupResponse
UNSUCCESSFUL OUTCOME E2setupFailure
PROCEDURE CODE id-E2setup
CRITICALITY reject
}
errorIndication E2AP-ELEMENTARY-PROCEDURE ::= {
INITIATING MESSAGE ErrorIndication
PROCEDURE CODE id-ErrorIndication
CRITICALITY ignore
}
reset E2AP-ELEMENTARY-PROCEDURE ::= {
INITIATING MESSAGE ResetRequest
SUCCESSFUL OUTCOME ResetResponse
PROCEDURE CODE id-Reset
CRITICALITY reject
}
ricControl E2AP-ELEMENTARY-PROCEDURE ::= {
INITIATING MESSAGE RICcontrolRequest
SUCCESSFUL OUTCOME RICcontrolAcknowledge
UNSUCCESSFUL OUTCOME RICcontrolFailure
PROCEDURE CODE id-RICcontrol
CRITICALITY reject
}

ricIndication E2AP-ELEMENTARY-PROCEDURE ::= {
INITIATING MESSAGE RICindication
PROCEDURE CODE id-RICindication
CRITICALITY ignore
}
ricServiceQuery E2AP-ELEMENTARY-PROCEDURE ::= {
INITIATING MESSAGE RICserviceQuery
PROCEDURE CODE id-RICserviceQuery
CRITICALITY ignore
}
ricServiceUpdate E2AP-ELEMENTARY-PROCEDURE ::= {
INITIATING MESSAGE RICserviceUpdate
SUCCESSFUL OUTCOME RICserviceUpdateAcknowledge
UNSUCCESSFUL OUTCOME RICserviceUpdateFailure
PROCEDURE CODE id-RICserviceUpdate
CRITICALITY reject
}
ricSubscription E2AP-ELEMENTARY-PROCEDURE ::= {
INITIATING MESSAGE RICsubscriptionRequest
SUCCESSFUL OUTCOME RICsubscriptionResponse
UNSUCCESSFUL OUTCOME RICsubscriptionFailure
PROCEDURE CODE id-RICsubscription
CRITICALITY reject
}
ricSubscriptionDelete E2AP-ELEMENTARY-PROCEDURE ::= {
INITIATING MESSAGE RICsubscriptionDeleteRequest
SUCCESSFUL OUTCOME RICsubscriptionDeleteResponse
UNSUCCESSFUL OUTCOME RICsubscriptionDeleteFailure
PROCEDURE CODE id-RICsubscriptionDelete
CRITICALITY reject
}
ricSubscriptionDeleteRequired E2AP-ELEMENTARY-PROCEDURE ::= {
INITIATING MESSAGE RICsubscriptionDeleteRequired
PROCEDURE CODE id-RICsubscriptionDeleteRequired
CRITICALITY ignore
}

END

E2AP-PDU-Contents {
iso(1) identified-organization(3) dod(6) internet(1) private(4) enterprise(1) 53148 e2(1) version2 (2)e2ap(1) e2ap-PDU-Contents (1) }

DEFINITIONS AUTOMATIC TAGS ::=

BEGIN

IMPORTS
Cause,
CriticalityDiagnostics,
E2nodeComponentConfiguration,
E2nodeComponentConfigurationAck,
E2nodeComponentID,
E2nodeComponentInterfaceType,
GlobalE2node-ID,
GlobalRIC-ID,
RANfunctionDefinition,
RANfunctionID,
RANfunctionOID,
RANfunctionRevision,
RICactionDefinition,
RICactionID,
RICactionType, RICcallProcessID,
RICcontrolAckRequest,
RICcontrolHeader,
RICcontrolMessage,
RICcontrolOutcome,
RICeventTriggerDefinition,
RICindicationHeader,
RICindicationMessage,
RICindicationSN,
RICindicationType,
RICrequestID,
RICsubsequentAction,
TimeToWait,
TNLinformation,
TNLusage,
TransactionID
FROM E2AP-IEs
ProtocolIE-Container{},
ProtocolIE-ContainerList{},
ProtocolIE-SingleContainer{},
E2AP-PROTOCOL-IES,
E2AP-PROTOCOL-IES-PAIR
FROM E2AP-Containers
id-Cause,
id-CriticalityDiagnostics,
id-E2connectionSetup,
id-E2connectionSetupFailed,
id-E2connectionSetupFailed-Item,
id-E2connectionFailed-Item,
id-E2connectionUpdate-Item,
id-E2connectionUpdateAdd,
id-E2connectionUpdateModify,
id-E2connectionUpdateRemove,
id-E2connectionUpdateRemove-Item,
id-E2nodeComponentConfigAddition,
id-E2nodeComponentConfigAddition-Item,
id-E2nodeComponentConfigAdditionAck,
id-E2nodeComponentConfigAdditionAck-Item,
id-E2nodeComponentConfigRemoval,
id-E2nodeComponentConfigRemoval-Item,
id-E2nodeComponentConfigRemovalAck,
id-E2nodeComponentConfigRemovalAck-Item,
id-E2nodeComponentConfigUpdate,
id-E2nodeComponentConfigUpdate-Item,
id-E2nodeComponentConfigUpdateAck,
id-E2nodeComponentConfigUpdateAck-Item,
id-E2nodeTNLassociationRemoval,
id-E2nodeTNLassociationRemoval-Item,
id-GlobalE2node-ID,
id-GlobalRIC-ID,
id-RANfunctionID,
id-RANfunctionID-Item,
id-RANfunctionIEcause-Item,
id-RANfunction-Item,
id-RANfunctionsAccepted,
id-RANfunctionsAdded,
id-RANfunctionsDeleted,
id-RANfunctionsModified,
id-RANfunctionsRejected,
id-RICaction-Admitted-Item,
id-RICactionID,
id-RICaction-NotAdmitted-Item,
id-RICactions-Admitted,
id-RICactions-NotAdmitted,
id-RICaction-ToBeSetup-Item,
id-RICcallProcessID, id-RICcontrolAckRequest,
id-RICcontrolHeader,
id-RICcontrolMessage, id-RICcontrolOutcome,
id-RICindicationHeader,
id-RICindicationMessage,
id-RICindicationSN,
id-RICindicationType,
id-RICrequestID,
id-RICserviceQuery,
id-RICsubscriptionDetails,
id-RICsubscriptionToBeRemoved,
id-RICsubscription-withCause-Item,
id-TimeToWait,
id-TNLinformation,
id-TransactionID,
maxofE2nodeComponents,
maxofRANfunctionID,
maxofRICactionID,
maxofRICrequestID,
maxofTNLA
FROM E2AP-Constants;
-- **************************************************************
--
-- MESSAGES FOR NEAR-RT RIC FUNCTIONAL PROCEDURES
--
-- **************************************************************
-- **************************************************************
--
-- RIC Subscription Elementary Procedure
--
-- **************************************************************
-- **************************************************************
--
-- RIC SUBSCRIPTION REQUEST
--
-- **************************************************************
RICsubscriptionRequest ::= SEQUENCE {
protocolIEs ProtocolIE-Container {{RICsubscriptionRequest-IEs}},
...
}
RICsubscriptionRequest-IEs E2AP-PROTOCOL-IES ::= {
{ ID id-RICrequestID CRITICALITY reject TYPE RICrequestID PRESENCE mandatory}|
{ ID id-RANfunctionID CRITICALITY reject TYPE RANfunctionID PRESENCE mandatory}|
{ ID id-RICsubscriptionDetails CRITICALITY reject TYPE RICsubscriptionDetails PRESENCE mandatory},
...
}
RICsubscriptionDetails ::= SEQUENCE {
ricEventTriggerDefinition RICeventTriggerDefinition,
ricAction-ToBeSetup-List RICactions-ToBeSetup-List,
...
}
RICactions-ToBeSetup-List ::= SEQUENCE (SIZE(1..maxofRICactionID)) OF ProtocolIE-SingleContainer { {RICaction-ToBeSetup-ItemIEs} }
RICaction-ToBeSetup-ItemIEs E2AP-PROTOCOL-IES ::= {
{ ID id-RICaction-ToBeSetup-Item CRITICALITY ignore TYPE RICaction-ToBeSetup-Item PRESENCE mandatory },
...
}
RICaction-ToBeSetup-Item ::= SEQUENCE {
ricActionID RICactionID,
ricActionType RICactionType,
ricActionDefinition RICactionDefinition OPTIONAL,
ricSubsequentAction RICsubsequentAction OPTIONAL,
...
}
-- **************************************************************
--
-- RIC SUBSCRIPTION RESPONSE
--
-- **************************************************************
RICsubscriptionResponse ::= SEQUENCE {
protocolIEs ProtocolIE-Container{{RICsubscriptionResponse-IEs}},
...
}
RICsubscriptionResponse-IEs E2AP-PROTOCOL-IES ::= {
{ ID id-RICrequestID CRITICALITY reject TYPE RICrequestID PRESENCE mandatory } |
{ ID id-RANfunctionID CRITICALITY reject TYPE RANfunctionID PRESENCE mandatory } |
{ ID id-RICactions-Admitted CRITICALITY reject TYPE RICaction-Admitted-ListPRESENCE mandatory } |
{ ID id-RICactions-NotAdmitted CRITICALITY reject TYPE RICaction-NotAdmitted-ListPRESENCE optional },
...
}
RICaction-Admitted-List ::= SEQUENCE (SIZE(1..maxofRICactionID)) OF ProtocolIE-SingleContainer{{RICaction-Admitted-ItemIEs}}
RICaction-Admitted-ItemIEs E2AP-PROTOCOL-IES ::= {
{ ID id-RICaction-Admitted-Item CRITICALITY ignore TYPE RICaction-Admitted-ItemPRESENCE mandatory },
...
}
RICaction-Admitted-Item ::= SEQUENCE {
ricActionID RICactionID,
...
}
RICaction-NotAdmitted-List ::= SEQUENCE (SIZE(0..maxofRICactionID)) OF ProtocolIE-SingleContainer { {RICaction-NotAdmitted-ItemIEs} }
RICaction-NotAdmitted-ItemIEs E2AP-PROTOCOL-IES ::= {
{ ID id-RICaction-NotAdmitted-Item CRITICALITY ignore TYPE RICaction-NotAdmitted-Item PRESENCE mandatory },
...
}
RICaction-NotAdmitted-Item ::= SEQUENCE {
ricActionID RICactionID,
cause Cause,
...
}
-- **************************************************************
--
-- RIC SUBSCRIPTION FAILURE
--
-- **************************************************************
RICsubscriptionFailure ::= SEQUENCE {
protocolIEs ProtocolIE-Container {{RICsubscriptionFailure-IEs}},
...
}
RICsubscriptionFailure-IEs E2AP-PROTOCOL-IES ::= {
{ ID id-RICrequestID CRITICALITY reject TYPE RICrequestID PRESENCE mandatory }|
{ ID id-RANfunctionID CRITICALITY reject TYPE RANfunctionID PRESENCE mandatory }|
{ ID id-Cause CRITICALITY reject TYPE Cause PRESENCE mandatory }|
{ ID id-CriticalityDiagnostics CRITICALITY ignore TYPE CriticalityDiagnostics PRESENCE optional },
...
}
-- **************************************************************
--
-- RIC Subscription Delete Elementary Procedure
--
-- **************************************************************
-- **************************************************************
--
-- RIC SUBSCRIPTION DELETE REQUEST
--
-- **************************************************************
RICsubscriptionDeleteRequest ::= SEQUENCE {
protocolIEs ProtocolIE-Container {{RICsubscriptionDeleteRequest-IEs}},
...
}
RICsubscriptionDeleteRequest-IEs E2AP-PROTOCOL-IES ::= {
{ ID id-RICrequestID CRITICALITY reject TYPE RICrequestID PRESENCE mandatory }|
{ ID id-RANfunctionID CRITICALITY reject TYPE RANfunctionID PRESENCE mandatory },
...
}
-- **************************************************************
--
-- RIC SUBSCRIPTION DELETE RESPONSE
--
-- **************************************************************
RICsubscriptionDeleteResponse ::= SEQUENCE {
protocolIEs ProtocolIE-Container {{RICsubscriptionDeleteResponse-IEs}},
...
}
RICsubscriptionDeleteResponse-IEs E2AP-PROTOCOL-IES ::= {
{ ID id-RICrequestID CRITICALITY reject TYPE RICrequestID PRESENCE mandatory }|
{ ID id-RANfunctionID CRITICALITY reject TYPE RANfunctionID PRESENCE mandatory },
...
}
-- **************************************************************
--
-- RIC SUBSCRIPTION DELETE FAILURE
--
-- **************************************************************
RICsubscriptionDeleteFailure ::= SEQUENCE {
protocolIEs ProtocolIE-Container {{RICsubscriptionDeleteFailure-IEs}},
...
}
RICsubscriptionDeleteFailure-IEs E2AP-PROTOCOL-IES ::= {
{ ID id-RICrequestID CRITICALITY reject TYPE RICrequestID PRESENCE mandatory }|
{ ID id-RANfunctionID CRITICALITY reject TYPE RANfunctionID PRESENCE mandatory }|
{ ID id-Cause CRITICALITY ignore TYPE Cause PRESENCE mandatory }|
{ ID id-CriticalityDiagnostics CRITICALITY ignore TYPE CriticalityDiagnostics PRESENCE optional },
...
}
-- **************************************************************
--
-- RIC Subscription Delete Required Elementary Procedure
--
-- **************************************************************
-- **************************************************************
--
-- RIC SUBSCRIPTION DELETE REQUIRED
--
-- **************************************************************
RICsubscriptionDeleteRequired ::= SEQUENCE {
protocolIEs ProtocolIE-Container {{RICsubscriptionDeleteRequired-IEs}},
...
}
RICsubscriptionDeleteRequired-IEs E2AP-PROTOCOL-IES ::= {
    { ID id-RICsubscriptionToBeRemoved CRITICALITY ignore TYPE RICsubscription-List-withCausePRESENCE mandatory },
...
}
RICsubscription-List-withCause ::= SEQUENCE (SIZE(1..maxofRICrequestID)) OF ProtocolIE-SingleContainer { {RICsubscription-withCause-ItemIEs} }
RICsubscription-withCause-ItemIEs E2AP-PROTOCOL-IES ::= {
{ ID id-RICsubscription-withCause-Item CRITICALITY ignore TYPE RICsubscription-withCause-Item PRESENCE mandatory },
...
}
RICsubscription-withCause-Item ::= SEQUENCE {
ricRequestID RICrequestID,
ranFunctionID RANfunctionID,
cause Cause,
...
}
-- **************************************************************
--
-- RIC Indication Elementary Procedure
--
-- **************************************************************
-- **************************************************************
--
-- RIC INDICATION
--
-- **************************************************************
RICindication ::= SEQUENCE {
protocolIEs ProtocolIE-Container {{RICindication-IEs}},
...
}
RICindication-IEs E2AP-PROTOCOL-IES ::= {
{ ID id-RICrequestID CRITICALITY reject TYPE RICrequestID PRESENCE mandatory }|
{ ID id-RANfunctionID CRITICALITY reject TYPE RANfunctionID PRESENCE mandatory }|
{ ID id-RICactionID CRITICALITY reject TYPE RICactionID PRESENCE mandatory }|
{ ID id-RICindicationSN CRITICALITY reject TYPE RICindicationSN PRESENCE optional }|
{ ID id-RICindicationType CRITICALITY reject TYPE RICindicationType PRESENCE mandatory }|
{ ID id-RICindicationHeader CRITICALITY reject TYPE RICindicationHeader PRESENCE mandatory }|
{ ID id-RICindicationMessage CRITICALITY reject TYPE RICindicationMessage PRESENCE mandatory }|
{ ID id-RICcallProcessID CRITICALITY reject TYPE RICcallProcessID PRESENCE optional },
...
}
-- **************************************************************
--
-- RIC Control Elementary Procedure
--
-- **************************************************************
-- **************************************************************
--
-- RIC CONTROL REQUEST
--
-- **************************************************************
RICcontrolRequest ::= SEQUENCE {
protocolIEs ProtocolIE-Container {{RICcontrolRequest-IEs}},
...
}
RICcontrolRequest-IEs E2AP-PROTOCOL-IES ::= { { ID id-RICrequestID CRITICALITY reject TYPE RICrequestID PRESENCE mandatory }|
{ ID id-RANfunctionID CRITICALITY reject TYPE RANfunctionID PRESENCE mandatory }|
{ ID id-RICcallProcessID CRITICALITY reject TYPE RICcallProcessID PRESENCE optional }|
{ ID id-RICcontrolHeader CRITICALITY reject TYPE RICcontrolHeader PRESENCE mandatory }|
{ ID id-RICcontrolMessage CRITICALITY reject TYPE RICcontrolMessage PRESENCE mandatory }|
{ ID id-RICcontrolAckRequest CRITICALITY reject TYPE RICcontrolAckRequest PRESENCE optional },
...
}
-- **************************************************************
--
-- RIC CONTROL ACKNOWLEDGE
--
-- **************************************************************
RICcontrolAcknowledge ::= SEQUENCE {
protocolIEs ProtocolIE-Container {{RICcontrolAcknowledge-IEs}},
...
}
RICcontrolAcknowledge-IEs E2AP-PROTOCOL-IES ::= {
{ ID id-RICrequestID CRITICALITY reject TYPE RICrequestID PRESENCE mandatory }|
{ ID id-RANfunctionID CRITICALITY reject TYPE RANfunctionID PRESENCE mandatory }|
{ ID id-RICcallProcessID CRITICALITY reject TYPE RICcallProcessID PRESENCE optional }|
{ ID id-RICcontrolOutcome CRITICALITY reject TYPE RICcontrolOutcome PRESENCE optional }, ...
}
-- **************************************************************
--
-- RIC CONTROL FAILURE
--
-- **************************************************************
RICcontrolFailure ::= SEQUENCE {
protocolIEs ProtocolIE-Container {{RICcontrolFailure-IEs}},
...
}
RICcontrolFailure-IEs E2AP-PROTOCOL-IES ::= { { ID id-RICrequestID CRITICALITY reject TYPE RICrequestID PRESENCE mandatory }|
{ ID id-RANfunctionID CRITICALITY reject TYPE RANfunctionID PRESENCE mandatory }|
{ ID id-RICcallProcessID CRITICALITY reject TYPE RICcallProcessID PRESENCE optional }|
{ ID id-Cause CRITICALITY ignore TYPE Cause PRESENCE mandatory }|
{ ID id-RICcontrolOutcome CRITICALITY reject TYPE RICcontrolOutcome PRESENCE optional },
...
}
-- **************************************************************
--
-- MESSAGES FOR GLOBAL PROCEDURES
--
-- **************************************************************
-- **************************************************************
--
-- Error Indication Elementary Procedure
--
-- **************************************************************
-- **************************************************************
--
-- ERROR INDICATION
--
-- **************************************************************
ErrorIndication ::= SEQUENCE {
protocolIEs ProtocolIE-Container {{ErrorIndication-IEs}},
...
}
ErrorIndication-IEs E2AP-PROTOCOL-IES ::= {
{ ID id-TransactionID CRITICALITY reject TYPE TransactionID PRESENCE optional }|
{ ID id-RICrequestID CRITICALITY reject TYPE RICrequestID PRESENCE optional }|
{ ID id-RANfunctionID CRITICALITY reject TYPE RANfunctionID PRESENCE optional }|
{ ID id-Cause CRITICALITY ignore TYPE Cause PRESENCE optional }|
{ ID id-CriticalityDiagnostics CRITICALITY ignore TYPE CriticalityDiagnostics PRESENCE optional }, ...
}
-- **************************************************************
--
-- E2 Setup Elementary Procedure
--
-- **************************************************************
-- **************************************************************
--
-- E2 SETUP REQUEST
--
-- **************************************************************
E2setupRequest ::= SEQUENCE {
protocolIEs ProtocolIE-Container { {E2setupRequestIEs} }, ...
}
E2setupRequestIEs E2AP-PROTOCOL-IES ::= {
{ ID id-TransactionID CRITICALITY reject TYPE TransactionID PRESENCE mandatory }|
{ ID id-GlobalE2node-ID CRITICALITY reject TYPE GlobalE2node-ID PRESENCE mandatory }|
{ ID id-RANfunctionsAdded CRITICALITY reject TYPE RANfunctions-List PRESENCE mandatory }|
{ ID id-E2nodeComponentConfigAddition CRITICALITY reject TYPE E2nodeComponentConfigAddition-List PRESENCE mandatory }, ...
}
-- **************************************************************
--
-- E2 SETUP RESPONSE
--
-- **************************************************************
E2setupResponse ::= SEQUENCE {
protocolIEs ProtocolIE-Container { {E2setupResponseIEs} },
...
}
E2setupResponseIEs E2AP-PROTOCOL-IES ::= {
{ ID id-TransactionID CRITICALITY reject TYPE TransactionID PRESENCE mandatory }| { ID id-GlobalRIC-ID CRITICALITY reject TYPE GlobalRIC-ID PRESENCE mandatory }|
{ ID id-RANfunctionsAccepted CRITICALITY reject TYPE RANfunctionsID-List PRESENCE optional }|
{ ID id-RANfunctionsRejected CRITICALITY reject TYPE RANfunctionsIDcause-List PRESENCE optional }|
{ ID id-E2nodeComponentConfigAdditionAck CRITICALITY reject TYPE E2nodeComponentConfigAdditionAck-List PRESENCE mandatory },
...
}
-- **************************************************************
--
-- E2 SETUP FAILURE
--
-- **************************************************************
E2setupFailure ::= SEQUENCE {
protocolIEs ProtocolIE-Container { {E2setupFailureIEs} },
...
}
E2setupFailureIEs E2AP-PROTOCOL-IES ::= {
{ ID id-TransactionID CRITICALITY reject TYPE TransactionID PRESENCE mandatory }|
{ ID id-CauseCRITICALITY ignore TYPE Cause PRESENCE mandatory }|
{ ID id-TimeToWait CRITICALITY ignore TYPE TimeToWait PRESENCE optional }|
{ ID id-CriticalityDiagnostics CRITICALITY ignore TYPE CriticalityDiagnostics PRESENCE optional }|
{ ID id-TNLinformation CRITICALITY ignore TYPE TNLinformation PRESENCE optional },
...
}
-- **************************************************************
--
-- E2 Connection Update Elementary Procedure
--
-- **************************************************************
-- **************************************************************
--
-- E2 CONNECTION UPDATE
--
-- **************************************************************
E2connectionUpdate ::= SEQUENCE {
protocolIEs ProtocolIE-Container {{E2connectionUpdate-IEs}},
...
}
E2connectionUpdate-IEs E2AP-PROTOCOL-IES ::= {
{ ID id-TransactionID CRITICALITY reject TYPE TransactionID PRESENCE mandatory }|
{ ID id-E2connectionUpdateAdd CRITICALITY reject TYPE E2connectionUpdate-List PRESENCE optional }|
{ ID id-E2connectionUpdateRemove CRITICALITY reject TYPE E2connectionUpdateRemove-List PRESENCE optional }|
{ ID id-E2connectionUpdateModify CRITICALITY reject TYPE E2connectionUpdate-List PRESENCE optional },
...
}
E2connectionUpdate-List ::= SEQUENCE (SIZE(1..maxofTNLA)) OF ProtocolIE-SingleContainer { {E2connectionUpdate-ItemIEs} }
E2connectionUpdate-ItemIEs E2AP-PROTOCOL-IES ::= {
{ ID id-E2connectionUpdate-Item CRITICALITY ignore TYPE E2connectionUpdate-Item PRESENCE mandatory },
...
}
E2connectionUpdate-Item ::= SEQUENCE {
tnlInformation TNLinformation,
tnlUsage TNLusage,
...
}
E2connectionUpdateRemove-List ::= SEQUENCE (SIZE(1..maxofTNLA)) OF ProtocolIE-SingleContainer { {E2connectionUpdateRemove-ItemIEs} }
E2connectionUpdateRemove-ItemIEs E2AP-PROTOCOL-IES ::= {
{ ID id-E2connectionUpdateRemove-Item CRITICALITY ignore TYPE E2connectionUpdateRemove-Item PRESENCE mandatory },
...
}
E2connectionUpdateRemove-Item ::= SEQUENCE {
tnlInformation TNLinformation,
...
}
-- **************************************************************
--
-- E2 CONNECTION UPDATE ACKNOWLEDGE
--
-- **************************************************************
E2connectionUpdateAcknowledge ::= SEQUENCE {
protocolIEs ProtocolIE-Container {{E2connectionUpdateAck-IEs}},
...
}
E2connectionUpdateAck-IEs E2AP-PROTOCOL-IES ::= {
{ ID id-TransactionID CRITICALITY reject TYPE TransactionID PRESENCE mandatory }|
{ ID id-E2connectionSetup CRITICALITY reject TYPE E2connectionUpdate-List PRESENCE optional }|
{ ID id-E2connectionSetupFailed CRITICALITY reject TYPE E2connectionSetupFailed-List PRESENCE optional },
...
}
E2connectionSetupFailed-List ::= SEQUENCE (SIZE(1..maxofTNLA)) OF ProtocolIE-SingleContainer { {E2connectionSetupFailed-ItemIEs} }
E2connectionSetupFailed-ItemIEs E2AP-PROTOCOL-IES ::= {
{ ID id-E2connectionSetupFailed-Item CRITICALITY ignore TYPE E2connectionSetupFailed-Item PRESENCE mandatory },
...
}
E2connectionSetupFailed-Item ::= SEQUENCE {
tnlInformation TNLinformation,
cause Cause,
...
}
-- **************************************************************
--
-- E2 CONNECTION UPDATE FAILURE
--
-- **************************************************************
E2connectionUpdateFailure ::= SEQUENCE {
protocolIEs ProtocolIE-Container {{E2connectionUpdateFailure-IEs}},
...
}
E2connectionUpdateFailure-IEs E2AP-PROTOCOL-IES ::= {
{ ID id-TransactionID CRITICALITY reject TYPE TransactionID PRESENCE mandatory }|
{ ID id-Cause CRITICALITY reject TYPE Cause PRESENCE optional }|
{ ID id-TimeToWait CRITICALITY ignore TYPE TimeToWait PRESENCE optional }|
{ ID id-CriticalityDiagnostics CRITICALITY ignore TYPE CriticalityDiagnostics PRESENCE optional },
...
}
-- **************************************************************
--
-- E2 Node Configuration Update Elementary Procedure
--
-- **************************************************************
-- **************************************************************
--
-- E2 NODE CONFIGURATION UPDATE
--
-- **************************************************************
E2nodeConfigurationUpdate ::= SEQUENCE {
protocolIEs ProtocolIE-Container {{E2nodeConfigurationUpdate-IEs}},
...
}
E2nodeConfigurationUpdate-IEs E2AP-PROTOCOL-IES ::= {
{ ID id-TransactionID CRITICALITY reject TYPE TransactionID PRESENCE mandatory }|
{ ID id-GlobalE2node-ID CRITICALITY reject TYPE GlobalE2node-ID PRESENCE optional }|
{ ID id-E2nodeComponentConfigAddition CRITICALITY reject TYPE E2nodeComponentConfigAddition-List PRESENCE optional }|
{ ID id-E2nodeComponentConfigUpdate CRITICALITY reject TYPE E2nodeComponentConfigUpdate-List PRESENCE optional }|
{ ID id-E2nodeComponentConfigRemoval CRITICALITY reject TYPE E2nodeComponentConfigRemoval-List PRESENCE optional }|
{ ID id-E2nodeTNLassociationRemoval CRITICALITY reject TYPE E2nodeTNLassociationRemoval-List PRESENCE optional },
...
}
E2nodeComponentConfigAddition-List ::= SEQUENCE (SIZE(1..maxofE2nodeComponents)) OF ProtocolIE-SingleContainer { {E2nodeComponentConfigAddition-ItemIEs} }
E2nodeComponentConfigAddition-ItemIEs E2AP-PROTOCOL-IES ::= {
{ ID id-E2nodeComponentConfigAddition-Item CRITICALITY reject TYPE E2nodeComponentConfigAddition-Item PRESENCE mandatory },
...
}
E2nodeComponentConfigAddition-Item ::= SEQUENCE {
e2nodeComponentInterfaceType E2nodeComponentInterfaceType,
e2nodeComponentID E2nodeComponentID,
e2nodeComponentConfiguration E2nodeComponentConfiguration,
...
}
E2nodeComponentConfigUpdate-List ::= SEQUENCE (SIZE(1..maxofE2nodeComponents)) OF ProtocolIE-SingleContainer { {E2nodeComponentConfigUpdate-ItemIEs} }
E2nodeComponentConfigUpdate-ItemIEs E2AP-PROTOCOL-IES ::= {
{ ID id-E2nodeComponentConfigUpdate-Item CRITICALITY reject TYPE E2nodeComponentConfigUpdate-Item PRESENCE mandatory },
...
}
E2nodeComponentConfigUpdate-Item ::= SEQUENCE {
e2nodeComponentInterfaceType E2nodeComponentInterfaceType,
e2nodeComponentID E2nodeComponentID,
e2nodeComponentConfiguration E2nodeComponentConfiguration,
...
}
E2nodeComponentConfigRemoval-List ::= SEQUENCE (SIZE(1..maxofE2nodeComponents)) OF ProtocolIE-SingleContainer { {E2nodeComponentConfigRemoval-ItemIEs} }
E2nodeComponentConfigRemoval-ItemIEs E2AP-PROTOCOL-IES ::= {
{ ID id-E2nodeComponentConfigRemoval-Item CRITICALITY reject TYPE E2nodeComponentConfigRemoval-Item PRESENCE mandatory },
...
}
E2nodeComponentConfigRemoval-Item ::= SEQUENCE {
e2nodeComponentInterfaceType E2nodeComponentInterfaceType,
e2nodeComponentID E2nodeComponentID,
...
}
E2nodeTNLassociationRemoval-List ::= SEQUENCE (SIZE(1..maxofTNLA)) OF ProtocolIE-SingleContainer { {E2nodeTNLassociationRemoval-ItemIEs} }
E2nodeTNLassociationRemoval-ItemIEs E2AP-PROTOCOL-IES ::= {
{ ID id-E2nodeTNLassociationRemoval-Item CRITICALITY reject TYPE E2nodeTNLassociationRemoval-Item PRESENCE mandatory },
...
}
E2nodeTNLassociationRemoval-Item ::= SEQUENCE {
tnlInformation TNLinformation,
tnlInformationRIC TNLinformation,
...
}
-- **************************************************************
--
-- E2 NODE CONFIGURATION UPDATE ACKNOWLEDGE
--
-- **************************************************************
E2nodeConfigurationUpdateAcknowledge ::= SEQUENCE {
protocolIEs ProtocolIE-Container {{E2nodeConfigurationUpdateAcknowledge-IEs}},
...
}
E2nodeConfigurationUpdateAcknowledge-IEs E2AP-PROTOCOL-IES ::= {
{ ID id-TransactionID CRITICALITY reject TYPE TransactionID PRESENCE mandatory }|
{ ID id-E2nodeComponentConfigAdditionAck CRITICALITY reject TYPE E2nodeComponentConfigAdditionAck-List PRESENCE optional }|
{ ID id-E2nodeComponentConfigUpdateAck CRITICALITY reject TYPE E2nodeComponentConfigUpdateAck-List PRESENCE optional }|
{ ID id-E2nodeComponentConfigRemovalAck CRITICALITY reject TYPE E2nodeComponentConfigRemovalAck-List PRESENCE optional },
...
}
E2nodeComponentConfigAdditionAck-List ::= SEQUENCE (SIZE(1..maxofE2nodeComponents)) OF ProtocolIE-SingleContainer { {E2nodeComponentConfigAdditionAck-ItemIEs} }
E2nodeComponentConfigAdditionAck-ItemIEs E2AP-PROTOCOL-IES ::= {
{ ID id-E2nodeComponentConfigAdditionAck-Item CRITICALITY reject TYPE E2nodeComponentConfigAdditionAck-Item PRESENCE mandatory },
...
}
E2nodeComponentConfigAdditionAck-Item ::= SEQUENCE {
e2nodeComponentInterfaceType E2nodeComponentInterfaceType,
e2nodeComponentID E2nodeComponentID,
e2nodeComponentConfigurationAck E2nodeComponentConfigurationAck,
...
}
E2nodeComponentConfigUpdateAck-List ::= SEQUENCE (SIZE(1..maxofE2nodeComponents)) OF ProtocolIE-SingleContainer { {E2nodeComponentConfigUpdateAck-ItemIEs} }
E2nodeComponentConfigUpdateAck-ItemIEs E2AP-PROTOCOL-IES ::= {
{ ID id-E2nodeComponentConfigUpdateAck-Item CRITICALITY reject TYPE E2nodeComponentConfigUpdateAck-Item PRESENCE mandatory },
...
}
E2nodeComponentConfigUpdateAck-Item ::= SEQUENCE {
e2nodeComponentInterfaceType E2nodeComponentInterfaceType,
e2nodeComponentID E2nodeComponentID,
e2nodeComponentConfigurationAck E2nodeComponentConfigurationAck,
...
}
E2nodeComponentConfigRemovalAck-List ::= SEQUENCE (SIZE(1..maxofE2nodeComponents)) OF ProtocolIE-SingleContainer { {E2nodeComponentConfigRemovalAck-ItemIEs} }
E2nodeComponentConfigRemovalAck-ItemIEs E2AP-PROTOCOL-IES ::= {
{ ID id-E2nodeComponentConfigRemovalAck-Item CRITICALITY reject TYPE E2nodeComponentConfigRemovalAck-Item PRESENCE mandatory },
...
}
E2nodeComponentConfigRemovalAck-Item ::= SEQUENCE {
e2nodeComponentInterfaceType E2nodeComponentInterfaceType,
e2nodeComponentID E2nodeComponentID,
e2nodeComponentConfigurationAck E2nodeComponentConfigurationAck,
...
}
-- **************************************************************
--
-- E2 NODE CONFIGURATION UPDATE FAILURE
--
-- **************************************************************
E2nodeConfigurationUpdateFailure ::= SEQUENCE {
protocolIEs ProtocolIE-Container {{E2nodeConfigurationUpdateFailure-IEs}},
...
}
E2nodeConfigurationUpdateFailure-IEs E2AP-PROTOCOL-IES ::= {
{ ID id-TransactionID CRITICALITY reject TYPE TransactionID PRESENCE mandatory }|
{ ID id-Cause CRITICALITY ignore TYPE Cause PRESENCE mandatory }|
{ ID id-TimeToWait CRITICALITY ignore TYPE TimeToWait PRESENCE optional }|
{ ID id-CriticalityDiagnostics CRITICALITY ignore TYPE CriticalityDiagnostics PRESENCE optional },
...
}
-- **************************************************************
--
-- Reset Elementary Procedure
--
-- **************************************************************
-- **************************************************************
--
-- RESET REQUEST
--
-- **************************************************************
ResetRequest ::= SEQUENCE {
protocolIEs ProtocolIE-Container { {ResetRequestIEs} },
...
}
ResetRequestIEs E2AP-PROTOCOL-IES ::= {
{ ID id-TransactionID CRITICALITY reject TYPE TransactionID PRESENCE mandatory }|
{ ID id-Cause CRITICALITY ignore TYPE Cause PRESENCE mandatory },
...
}
-- **************************************************************
--
-- RESET RESPONSE
--
-- **************************************************************
ResetResponse ::= SEQUENCE {
protocolIEs ProtocolIE-Container { {ResetResponseIEs} },
...
}
ResetResponseIEs E2AP-PROTOCOL-IES ::= {
{ ID id-TransactionID CRITICALITY reject TYPE TransactionID PRESENCE mandatory }|
{ ID id-CriticalityDiagnostics CRITICALITY ignore TYPE CriticalityDiagnostics PRESENCE optional },
...
}
-- **************************************************************
--
-- RIC Service Update Elementary Procedure
--
-- **************************************************************
-- **************************************************************
--
-- RIC SERVICE UPDATE
--
-- **************************************************************
RICserviceUpdate ::= SEQUENCE { protocolIEs ProtocolIE-Container {{RICserviceUpdate-IEs}},
...
}
RICserviceUpdate-IEs E2AP-PROTOCOL-IES ::= {
{ ID id-TransactionID CRITICALITY reject TYPE TransactionID PRESENCE mandatory }| { ID id-RANfunctionsAdded CRITICALITY reject TYPE RANfunctions-List PRESENCE optional }|
{ ID id-RANfunctionsModified CRITICALITY reject TYPE RANfunctions-List PRESENCE optional }|
{ ID id-RANfunctionsDeleted CRITICALITY reject TYPE RANfunctionsID-List PRESENCE optional },
...
}
RANfunctions-List ::= SEQUENCE (SIZE(1..maxofRANfunctionID)) OF ProtocolIE-SingleContainer { {RANfunction-ItemIEs} }
RANfunction-ItemIEs E2AP-PROTOCOL-IES ::= {
{ ID id-RANfunction-Item CRITICALITY ignore TYPE RANfunction-Item PRESENCE mandatory },
...
}
RANfunction-Item ::= SEQUENCE {
ranFunctionID RANfunctionID,
ranFunctionDefinition RANfunctionDefinition,
ranFunctionRevision RANfunctionRevision,
ranFunctionOID RANfunctionOID,
...
}
RANfunctionsID-List ::= SEQUENCE (SIZE(1..maxofRANfunctionID)) OF ProtocolIE-SingleContainer{{RANfunctionID-ItemIEs}}
RANfunctionID-ItemIEs E2AP-PROTOCOL-IES ::= {
{ ID id-RANfunctionID-Item CRITICALITY ignore TYPE RANfunctionID-Item PRESENCE mandatory },
...
}
RANfunctionID-Item ::= SEQUENCE {
ranFunctionID RANfunctionID,
ranFunctionRevision RANfunctionRevision,
...
}
-- **************************************************************
--
-- RIC SERVICE UPDATE ACKNOWLEDGE
--
-- **************************************************************
RICserviceUpdateAcknowledge ::= SEQUENCE {
protocolIEs ProtocolIE-Container {{RICserviceUpdateAcknowledge-IEs}},
...
}
RICserviceUpdateAcknowledge-IEs E2AP-PROTOCOL-IES ::= {
{ ID id-TransactionID CRITICALITY reject TYPE TransactionID PRESENCE mandatory }|
{ ID id-RANfunctionsAccepted CRITICALITY reject TYPE RANfunctionsID-List PRESENCE mandatory }|
{ ID id-RANfunctionsRejected CRITICALITY reject TYPE RANfunctionsIDcause-List PRESENCE optional },
...
}
RANfunctionsIDcause-List ::= SEQUENCE (SIZE(1..maxofRANfunctionID)) OF ProtocolIE-SingleContainer { {RANfunctionIDcause-ItemIEs} }
RANfunctionIDcause-ItemIEs E2AP-PROTOCOL-IES ::= {
{ ID id-RANfunctionIEcause-Item CRITICALITY ignore TYPE RANfunctionIDcause-Item PRESENCE mandatory },
...
}
RANfunctionIDcause-Item ::= SEQUENCE {
ranFunctionID RANfunctionID,
cause Cause,
...
}
-- **************************************************************
--
-- RIC SERVICE UPDATE FAILURE
--
-- **************************************************************
RICserviceUpdateFailure ::= SEQUENCE {
protocolIEs ProtocolIE-Container {{RICserviceUpdateFailure-IEs}},
...
}
RICserviceUpdateFailure-IEs E2AP-PROTOCOL-IES ::= {
{ ID id-TransactionID CRITICALITY reject TYPE TransactionID PRESENCE mandatory }|
{ ID id-Cause CRITICALITY reject TYPE Cause PRESENCE mandatory }|
{ ID id-TimeToWait CRITICALITY ignore TYPE TimeToWait PRESENCE optional }|
{ ID id-CriticalityDiagnostics CRITICALITY ignore TYPE CriticalityDiagnostics PRESENCE optional },
...
}
-- **************************************************************
--
-- RIC Service Query Elementary Procedure
--
-- **************************************************************
-- **************************************************************
--
-- RIC SERVICE QUERY
--
-- **************************************************************
RICserviceQuery ::= SEQUENCE {
protocolIEs ProtocolIE-Container {{RICserviceQuery-IEs}},
...
}
RICserviceQuery-IEs E2AP-PROTOCOL-IES ::= {
{ ID id-TransactionID CRITICALITY reject TYPE TransactionID PRESENCE mandatory }|
{ ID id-RANfunctionsAccepted CRITICALITY reject TYPE RANfunctionsID-List PRESENCE optional },
...
}
END
-- E2AP
-- Information Element Definitions
--
-- **************************************************************
E2AP-IEs {
iso(1) identified-organization(3) dod(6) internet(1) private(4) enterprise(1) 53148 e2(1) version2 (2)e2ap(1) e2ap-IEs (2)}
DEFINITIONS AUTOMATIC TAGS ::=
BEGIN
IMPORTS
Criticality,
Presence,
ProcedureCode,
ProtocolIE-ID,
TriggeringMessage
FROM E2AP-CommonDataTypes
maxnoofErrors,
maxProtocolIEs
FROM E2AP-Constants;
-- A
-- **************************************************************
-- [New for E2AP v02.00] copied from 3GPP 38.413 (NGAP) IEs
-- **************************************************************
AMFName ::= PrintableString (SIZE(1..150, ...))
-- B
-- C
Cause ::= CHOICE {
ricRequest CauseRICrequest,
ricService CauseRICservice,
e2Node CauseE2node,
transport CauseTransport,
protocol CauseProtocol,
misc CauseMisc,
...
}
CauseE2node ::= ENUMERATED {
e2node-component-unknown,
...
}
CauseMisc ::= ENUMERATED {
control-processing-overload,
hardware-failure,
om-intervention,
unspecified,
...
}
CauseProtocol ::= ENUMERATED {
transfer-syntax-error,
abstract-syntax-error-reject,
abstract-syntax-error-ignore-and-notify,
message-not-compatible-with-receiver-state,
semantic-error,
abstract-syntax-error-falsely-constructed-message,
unspecified,
...
}
CauseRICrequest ::= ENUMERATED {
ran-function-id-invalid,
action-not-supported,
excessive-actions,
duplicate-action,
duplicate-event-trigger,
function-resource-limit,
request-id-unknown,
inconsistent-action-subsequent-action-sequence,
control-message-invalid,
ric-call-process-id-invalid,
control-timer-expired,
control-failed-to-execute,
system-not-ready,
unspecified,
...
}
CauseRICservice ::= ENUMERATED{
ran-function-not-supported,
excessive-functions,
ric-resource-limit,
...
}
CauseTransport ::= ENUMERATED {
unspecified,
transport-resource-unavailable,
...
}
-- **************************************************************
-- copied from 3GPP 38.413 (NGAP) IEs
-- note: ie-Extensions removed
-- **************************************************************
CriticalityDiagnostics ::= SEQUENCE {
procedureCode ProcedureCode OPTIONAL,
triggeringMessage TriggeringMessage OPTIONAL,
procedureCriticality Criticality OPTIONAL,
ricRequestorID RICrequestID OPTIONAL,
iEsCriticalityDiagnostics CriticalityDiagnostics-IE-List OPTIONAL,
...
}
CriticalityDiagnostics-IE-List ::= SEQUENCE (SIZE(1..maxnoofErrors)) OF CriticalityDiagnostics-IE-Item
CriticalityDiagnostics-IE-Item ::= SEQUENCE {
iECriticality Criticality,
iE-ID ProtocolIE-ID,
typeOfError TypeOfError,
...
}
-- D
-- E
-- Following IE used to carry 3GPP defined SETUP and RAN Configuration messages defined in F1AP, E1AP, XnAP, etc.
E2nodeComponentConfiguration ::= SEQUENCE{
e2nodeComponentRequestPart OCTET STRING,
e2nodeComponentResponsePart OCTET STRING,
...
}
E2nodeComponentConfigurationAck ::= SEQUENCE{
updateOutcome ENUMERATED {success, failure, ...},
failureCause Cause OPTIONAL,
...
}
E2nodeComponentInterfaceType ::= ENUMERATED {ng, xn, e1, f1, w1, s1, x2,...}
E2nodeComponentID ::= CHOICE{
e2nodeComponentInterfaceTypeNG E2nodeComponentInterfaceNG,
e2nodeComponentInterfaceTypeXn E2nodeComponentInterfaceXn,
e2nodeComponentInterfaceTypeE1 E2nodeComponentInterfaceE1,
e2nodeComponentInterfaceTypeF1 E2nodeComponentInterfaceF1,
e2nodeComponentInterfaceTypeW1 E2nodeComponentInterfaceW1,
e2nodeComponentInterfaceTypeS1 E2nodeComponentInterfaceS1,
e2nodeComponentInterfaceTypeX2 E2nodeComponentInterfaceX2,
...
}
E2nodeComponentInterfaceE1 ::= SEQUENCE{
gNB-CU-CP-ID GNB-CU-UP-ID,
...
}
E2nodeComponentInterfaceF1 ::= SEQUENCE{
gNB-DU-ID GNB-DU-ID,
...
}
E2nodeComponentInterfaceNG ::= SEQUENCE{
amf-name AMFName,
...
}
E2nodeComponentInterfaceS1 ::= SEQUENCE{
mme-name MMEname,
...
}
E2nodeComponentInterfaceX2 ::= SEQUENCE{
global-eNB-ID GlobalENB-ID OPTIONAL,
global-en-gNB-ID GlobalenGNB-ID OPTIONAL,
...
}
E2nodeComponentInterfaceXn ::= SEQUENCE{
global-NG-RAN-Node-ID GlobalNG-RANNode-ID,
...
}
E2nodeComponentInterfaceW1 ::= SEQUENCE{
ng-eNB-DU-ID NGENB-DU-ID,
...
}
-- **************************************************************
-- copied from 3GPP 36.423 (X2AP) IEs
-- note: ie-Extensions removed
-- **************************************************************
ENB-ID ::= CHOICE {
macro-eNB-ID BIT STRING (SIZE (20)),
home-eNB-ID BIT STRING (SIZE (28)),
... ,
short-Macro-eNB-ID BIT STRING (SIZE(18)),
long-Macro-eNB-ID BIT STRING (SIZE(21))
}
-- **************************************************************
-- copied from 3GPP 38.423 (XnAP) IEs
-- **************************************************************
ENB-ID-Choice ::= CHOICE {
enb-ID-macro BIT STRING (SIZE(20)),
enb-ID-shortmacro BIT STRING (SIZE(18)),
enb-ID-longmacro BIT STRING (SIZE(21)),
...
}
-- **************************************************************
-- copied from 3GPP 36.423 (X2AP) IEs
-- note: ie-Extensions removed
-- Note: to avoid duplicate names with XnAP, GNB-ID renamed ENGNB-ID, GlobalGNB-ID renamed GlobalenGNB-ID
-- **************************************************************
ENGNB-ID ::= CHOICE {
gNB-ID BIT STRING (SIZE (22..32)),
...
}
-- F
-- G
GlobalE2node-ID ::= CHOICE{ gNB GlobalE2node-gNB-ID,
en-gNB GlobalE2node-en-gNB-ID, ng-eNB GlobalE2node-ng-eNB-ID,
eNB GlobalE2node-eNB-ID,
...
}
GlobalE2node-en-gNB-ID ::= SEQUENCE{
global-en-gNB-ID GlobalenGNB-ID,
en-gNB-CU-UP-ID GNB-CU-UP-ID OPTIONAL,
en-gNB-DU-ID GNB-DU-ID OPTIONAL,
...
}
GlobalE2node-eNB-ID ::= SEQUENCE{
global-eNB-ID GlobalENB-ID,
...
}
GlobalE2node-gNB-ID ::= SEQUENCE{
global-gNB-ID GlobalgNB-ID,
global-en-gNB-ID GlobalenGNB-ID OPTIONAL,
gNB-CU-UP-ID GNB-CU-UP-ID OPTIONAL,
gNB-DU-ID GNB-DU-ID OPTIONAL,
...
}
GlobalE2node-ng-eNB-ID ::= SEQUENCE{
global-ng-eNB-ID GlobalngeNB-ID,
global-eNB-ID GlobalENB-ID OPTIONAL,
ngENB-DU-ID NGENB-DU-ID OPTIONAL,
...
}
-- **************************************************************
-- copied from 3GPP 36.423 (X2AP) IEs
-- note: ie-Extensions removed
-- **************************************************************
GlobalENB-ID ::= SEQUENCE {
pLMN-Identity PLMN-Identity,
eNB-ID ENB-ID,
...
}
-- **************************************************************
-- copied from 3GPP 36.423 (X2AP) IEs
-- Note: to avoid duplicate names with XnAP, GNB-ID renamed ENGNB-ID, GlobalGNB-ID renamed GlobalenGNB-ID
-- **************************************************************
GlobalenGNB-ID ::= SEQUENCE {
pLMN-Identity PLMN-Identity,
gNB-ID ENGNB-ID,
...
}
-- **************************************************************
-- copied from 3GPP 38.423 (XnAP) IEs
-- **************************************************************
GlobalgNB-ID ::= SEQUENCE {
plmn-id PLMN-Identity,
gnb-id GNB-ID-Choice,
...
}
-- **************************************************************
-- copied from 3GPP 38.423 (XnAP) IEs
-- **************************************************************
GlobalngeNB-ID ::= SEQUENCE {
plmn-id PLMN-Identity,
enb-id ENB-ID-Choice,
...
}
-- **************************************************************
-- [NEW for E2AP v02.00] copied from 3GPP 38.423 (XnAP) IEs
-- Note: extension field removed
-- **************************************************************
GlobalNG-RANNode-ID ::= CHOICE {
gNB GlobalgNB-ID,
ng-eNB GlobalngeNB-ID,
...
}
GlobalRIC-ID ::= SEQUENCE{
pLMN-Identity PLMN-Identity,
ric-ID BIT STRING (SIZE (20)),
...
}
-- **************************************************************
-- copied from 3GPP 38.463 (E1AP) IEs
-- **************************************************************
GNB-CU-UP-ID::= INTEGER (0..68719476735)
GNB-DU-ID::= INTEGER (0..68719476735)
-- **************************************************************
-- copied from 3GPP 38.423 (XnAP) IEs
-- **************************************************************
GNB-ID-Choice ::= CHOICE {
gnb-ID BIT STRING (SIZE(22..32)),
...
}
-- H
-- I
-- J
-- K
-- L
-- M
-- **************************************************************
-- [New for E2AP v02.00] copied from 3GPP 36.413 (S1AP) IEs
-- **************************************************************
MMEname ::= PrintableString (SIZE (1..150,...))
-- N
-- **************************************************************
-- copied from 3GPP 37.473 (W1AP) IEs
-- **************************************************************
NGENB-DU-ID ::= INTEGER (0..68719476735)
-- O
-- P
-- **************************************************************
-- copied from 3GPP 36.423 (X2AP) IEs
-- **************************************************************
PLMN-Identity ::= OCTET STRING (SIZE(3))
-- Q
-- R
-- **************************************************************
-- Following IE defined in E2SM
-- **************************************************************
RANfunctionDefinition ::= OCTET STRING
RANfunctionID ::= INTEGER (0..4095)
RANfunctionOID ::= PrintableString(SIZE(1..1000,...))
RANfunctionRevision ::= INTEGER (0..4095)
-- **************************************************************
-- Following IE defined in E2SM
-- **************************************************************
RICactionDefinition ::= OCTET STRING
RICactionID ::= INTEGER (0..255)
RICactionType ::= ENUMERATED{
report,
insert,
policy,
...
}
-- **************************************************************
-- Following IE defined in E2SM
-- **************************************************************
RICcallProcessID ::= OCTET STRING
RICcontrolAckRequest ::= ENUMERATED{
noAck,
ack,
...
}
-- **************************************************************
-- Following IE defined in E2SM
-- **************************************************************
RICcontrolHeader ::= OCTET STRING
-- **************************************************************
-- Following IE defined in E2SM
-- **************************************************************
RICcontrolMessage ::= OCTET STRING
-- **************************************************************
-- Following IE defined in E2SM
-- **************************************************************
RICcontrolOutcome ::= OCTET STRING
-- **************************************************************
-- Following IE defined in E2SM
-- **************************************************************
RICeventTriggerDefinition ::= OCTET STRING
-- **************************************************************
-- Following IE defined in E2SM
-- **************************************************************
RICindicationHeader ::= OCTET STRING
-- **************************************************************
-- Following IE defined in E2SM
-- **************************************************************
RICindicationMessage ::= OCTET STRING
RICindicationSN ::= INTEGER (0..65535)
RICindicationType ::= ENUMERATED{
report,
insert,
...
}
RICrequestID ::= SEQUENCE {
ricRequestorID INTEGER (0..65535),
ricInstanceID INTEGER (0..65535),
...
}
RICsubsequentAction ::=SEQUENCE{
ricSubsequentActionType RICsubsequentActionType,
ricTimeToWait RICtimeToWait,
...
}
RICsubsequentActionType ::= ENUMERATED{
continue,
wait,
...
}
RICtimeToWait ::= ENUMERATED{
w1ms,
w2ms,
w5ms,
w10ms,
w20ms,
w30ms,
w40ms,
w50ms,
w100ms,
w200ms,
w500ms,
w1s,
w2s,
w5s,
w10s,
w20s,
w60s,
...
}
-- S
-- T
-- **************************************************************
-- copied from 3GPP 38.413 (NGAP) IEs
-- **************************************************************
TimeToWait ::= ENUMERATED {v1s, v2s, v5s, v10s, v20s, v60s, ...}
TNLinformation ::= SEQUENCE{
tnlAddress BIT STRING (SIZE(1..160,...)),
tnlPort BIT STRING (SIZE(16)) OPTIONAL,
...
}
TNLusage ::= ENUMERATED{ric-service, support-function, both, ...}
TransactionID ::= INTEGER (0..255,...)
-- **************************************************************
-- copied from 3GPP 38.413 (NGAP) IEs
-- **************************************************************
TypeOfError ::= ENUMERATED {
not-understood,
missing,
...
}

-- U
-- V
-- W
-- X
-- Y
-- Z
END
-- Derived from 3GPP 38.413 (NGAP)
--
-- **************************************************************
E2AP-CommonDataTypes {
iso(1) identified-organization(3) dod(6) internet(1) private(4) enterprise(1) 53148 e2(1) version2 (2)e2ap(1) e2ap-CommonDataTypes (3) }
DEFINITIONS AUTOMATIC TAGS ::=
BEGIN
Criticality ::= ENUMERATED { reject, ignore, notify }
Presence ::= ENUMERATED { optional, conditional, mandatory }
ProcedureCode ::= INTEGER (0..255)
ProtocolIE-ID ::= INTEGER (0..65535)
TriggeringMessage ::= ENUMERATED { initiating-message, successful-outcome, unsuccessfull-outcome }

END
-- Constant definitions
--
-- **************************************************************
E2AP-Constants {
iso(1) identified-organization(3) dod(6) internet(1) private(4) enterprise(1) 53148 e2(1) version2 (2)e2ap(1) e2ap-Constants (4) }
DEFINITIONS AUTOMATIC TAGS ::=
BEGIN
IMPORTS
ProcedureCode,
ProtocolIE-ID
FROM E2AP-CommonDataTypes;
-- **************************************************************
--
-- Elementary Procedures
--
-- **************************************************************
id-E2setup ProcedureCode ::= 1
id-ErrorIndication ProcedureCode ::= 2
id-Reset ProcedureCode ::= 3
id-RICcontrol ProcedureCode ::= 4
id-RICindication ProcedureCode ::= 5
id-RICserviceQuery ProcedureCode ::= 6
id-RICserviceUpdate ProcedureCode ::= 7
id-RICsubscription ProcedureCode ::= 8
id-RICsubscriptionDelete ProcedureCode ::= 9
id-E2nodeConfigurationUpdate ProcedureCode ::= 10
id-E2connectionUpdate ProcedureCode ::= 11
id-RICsubscriptionDeleteRequired ProcedureCode ::= 12
-- **************************************************************
--
-- Extension constants
--
-- **************************************************************
maxProtocolIEs INTEGER ::= 65535
-- **************************************************************
-- Lists
--
-- **************************************************************
maxnoofErrors INTEGER ::= 256
maxofE2nodeComponents INTEGER ::= 1024
maxofRANfunctionID INTEGER ::= 256
maxofRICactionID INTEGER ::= 16
maxofTNLA INTEGER ::= 32
maxofRICrequestID INTEGER ::= 4294967295
-- **************************************************************
--
-- IEs
--
-- **************************************************************
id-Cause ProtocolIE-ID ::= 1
id-CriticalityDiagnostics ProtocolIE-ID ::= 2
id-GlobalE2node-ID ProtocolIE-ID ::= 3
id-GlobalRIC-ID ProtocolIE-ID ::= 4
id-RANfunctionID ProtocolIE-ID ::= 5
id-RANfunctionID-Item ProtocolIE-ID ::= 6
id-RANfunctionIEcause-Item ProtocolIE-ID ::= 7
id-RANfunction-Item ProtocolIE-ID ::= 8
id-RANfunctionsAccepted ProtocolIE-ID ::= 9
id-RANfunctionsAdded ProtocolIE-ID ::= 10
id-RANfunctionsDeleted ProtocolIE-ID ::= 11
id-RANfunctionsModified ProtocolIE-ID ::= 12
id-RANfunctionsRejected ProtocolIE-ID ::= 13
id-RICaction-Admitted-Item ProtocolIE-ID ::= 14
id-RICactionID ProtocolIE-ID ::= 15
id-RICaction-NotAdmitted-Item ProtocolIE-ID ::= 16
id-RICactions-Admitted ProtocolIE-ID ::= 17
id-RICactions-NotAdmitted ProtocolIE-ID ::= 18
id-RICaction-ToBeSetup-Item ProtocolIE-ID ::= 19
id-RICcallProcessID ProtocolIE-ID ::= 20
id-RICcontrolAckRequest ProtocolIE-ID ::= 21
id-RICcontrolHeader ProtocolIE-ID ::= 22
id-RICcontrolMessage ProtocolIE-ID ::= 23
id-RICcontrolStatus ProtocolIE-ID ::= 24
id-RICindicationHeader ProtocolIE-ID ::= 25
id-RICindicationMessage ProtocolIE-ID ::= 26
id-RICindicationSN ProtocolIE-ID ::= 27
id-RICindicationType ProtocolIE-ID ::= 28
id-RICrequestID ProtocolIE-ID ::= 29
id-RICsubscriptionDetails ProtocolIE-ID ::= 30
id-TimeToWait ProtocolIE-ID ::= 31
id-RICcontrolOutcome ProtocolIE-ID ::= 32
id-E2nodeComponentConfigUpdate ProtocolIE-ID ::= 33
id-E2nodeComponentConfigUpdate-Item ProtocolIE-ID ::= 34
id-E2nodeComponentConfigUpdateAck ProtocolIE-ID ::= 35
id-E2nodeComponentConfigUpdateAck-Item ProtocolIE-ID ::= 36
id-E2connectionSetup ProtocolIE-ID ::= 39
id-E2connectionSetupFailed ProtocolIE-ID ::= 40
id-E2connectionSetupFailed-Item ProtocolIE-ID ::= 41
id-E2connectionFailed-Item ProtocolIE-ID ::= 42
id-E2connectionUpdate-Item ProtocolIE-ID ::= 43
id-E2connectionUpdateAdd ProtocolIE-ID ::= 44
id-E2connectionUpdateModify ProtocolIE-ID ::= 45
id-E2connectionUpdateRemove ProtocolIE-ID ::= 46
id-E2connectionUpdateRemove-Item ProtocolIE-ID ::= 47
id-TNLinformation ProtocolIE-ID ::= 48
id-TransactionID ProtocolIE-ID ::= 49
id-E2nodeComponentConfigAddition ProtocolIE-ID ::= 50
id-E2nodeComponentConfigAddition-Item ProtocolIE-ID ::= 51
id-E2nodeComponentConfigAdditionAck ProtocolIE-ID ::= 52
id-E2nodeComponentConfigAdditionAck-Item ProtocolIE-ID ::= 53
id-E2nodeComponentConfigRemoval ProtocolIE-ID ::= 54
id-E2nodeComponentConfigRemoval-Item ProtocolIE-ID ::= 55
id-E2nodeComponentConfigRemovalAck ProtocolIE-ID ::= 56
id-E2nodeComponentConfigRemovalAck-Item ProtocolIE-ID ::= 57
id-E2nodeTNLassociationRemoval ProtocolIE-ID ::= 58
id-E2nodeTNLassociationRemoval-Item ProtocolIE-ID ::= 59
id-RICsubscriptionToBeRemoved ProtocolIE-ID ::= 50
id-RICsubscription-withCause-Item ProtocolIE-ID ::= 51

END
-- Container definitions
--
-- derived from 3GPP 38.413 (NGAP)
-- **************************************************************
E2AP-Containers {
iso(1) identified-organization(3) dod(6) internet(1) private(4) enterprise(1) 53148 e2(1) version2 (2)e2ap(1) e2ap-Containers (5) }
DEFINITIONS AUTOMATIC TAGS ::=
BEGIN
-- **************************************************************
--
-- IE parameter types from other modules.
--
-- **************************************************************
IMPORTS
Criticality,
Presence,
ProtocolIE-ID
FROM E2AP-CommonDataTypes
maxProtocolIEs
FROM E2AP-Constants;
-- **************************************************************
--
-- Class Definition for Protocol IEs
--
-- **************************************************************
E2AP-PROTOCOL-IES ::= CLASS {
&id ProtocolIE-ID UNIQUE,
&criticality Criticality,
&Value,
&presence Presence
}
WITH SYNTAX {
ID &id
CRITICALITY &criticality
TYPE &Value
PRESENCE &presence
}
-- **************************************************************
--
-- Class Definition for Protocol IEs
--
-- **************************************************************
E2AP-PROTOCOL-IES-PAIR ::= CLASS {
&id ProtocolIE-ID UNIQUE,
&firstCriticality Criticality,
&FirstValue,
&secondCriticality Criticality,
&SecondValue,
&presence Presence
}
WITH SYNTAX {
ID &id
FIRST CRITICALITY &firstCriticality
FIRST TYPE &FirstValue
SECOND CRITICALITY &secondCriticality
SECOND TYPE &SecondValue
PRESENCE &presence
}
-- Container for Protocol IEs
--
-- **************************************************************
ProtocolIE-Container {E2AP-PROTOCOL-IES : IEsSetParam} ::= SEQUENCE (SIZE (0..maxProtocolIEs)) OF
ProtocolIE-Field {{IEsSetParam}}
ProtocolIE-SingleContainer {E2AP-PROTOCOL-IES : IEsSetParam} ::=
ProtocolIE-Field {{IEsSetParam}}
ProtocolIE-Field {E2AP-PROTOCOL-IES : IEsSetParam} ::= SEQUENCE { id E2AP-PROTOCOL-IES.&id ({IEsSetParam}),
criticality E2AP-PROTOCOL-IES.&criticality ({IEsSetParam}{@id}),
value E2AP-PROTOCOL-IES.&Value ({IEsSetParam}{@id})
}
-- **************************************************************
--
-- Container for Protocol IE Pairs
--
-- **************************************************************
ProtocolIE-ContainerPair {E2AP-PROTOCOL-IES-PAIR : IEsSetParam} ::=
SEQUENCE (SIZE (0..maxProtocolIEs)) OF
ProtocolIE-FieldPair {{IEsSetParam}}
ProtocolIE-FieldPair {E2AP-PROTOCOL-IES-PAIR : IEsSetParam} ::= SEQUENCE {
id E2AP-PROTOCOL-IES-PAIR.&id ({IEsSetParam}),
firstCriticality E2AP-PROTOCOL-IES-PAIR.&firstCriticality ({IEsSetParam}{@id}),
firstValue E2AP-PROTOCOL-IES-PAIR.&FirstValue ({IEsSetParam}{@id}),
secondCriticality E2AP-PROTOCOL-IES-PAIR.&secondCriticality ({IEsSetParam}{@id}),
secondValue E2AP-PROTOCOL-IES-PAIR.&SecondValue ({IEsSetParam}{@id})
}
-- **************************************************************
--
-- Container Lists for Protocol IE Containers
--
-- **************************************************************
ProtocolIE-ContainerList {INTEGER : lowerBound, INTEGER : upperBound, E2AP-PROTOCOL-IES : IEsSetParam} ::=
SEQUENCE (SIZE (lowerBound..upperBound)) OF
ProtocolIE-SingleContainer {{IEsSetParam}}
ProtocolIE-ContainerPairList {INTEGER : lowerBound, INTEGER : upperBound, E2AP-PROTOCOL-IES-PAIR : IEsSetParam} ::=
SEQUENCE (SIZE (lowerBound..upperBound)) OF
ProtocolIE-ContainerPair {{IEsSetParam}}
END
-- ASN1STOP
